#usage "<b>Cycle through visible board layers quickly</b> <hr>"
       "Useful to quickly enable/disable/cycle through a set of related layers. No parameters necessary.<p>"

       "For example, <b>disabling</b> <font color='red'>Top</font>, tDocu, tPlace, tOrigins, tNames, tKeepout, and tRestrict, while <b>enabling</b> the related <font color='blue'>Bottom</font> layers.<p>"

       "Tip: Assign a hotkey with: <br>"
       "<tt>ASSIGN Ctrl+L 'run throughLayers.ulp';</tt>"
       "<p>"
       "<author><b>Author:</b> <a href='https://twitter.com/samykamkar'>Samy Kamkar</a> || <a href='https://samy.pl'>https://samy.pl</a> || <a href='mailto:ulp@samy.pl'>ulp@samy.pl</a></author> <br>"
       "<b>Date:</b> 2017/02/27 <p>"

       "<img width=480 src='https://raw.githubusercontent.com/samyk/samytools/master/eagle/img/throughLayers1.png'> <br>"
       "<img width=480 src='https://raw.githubusercontent.com/samyk/samytools/master/eagle/img/throughLayers2.png'> <br>"
       "<img width=480 src='https://raw.githubusercontent.com/samyk/samytools/master/eagle/img/throughLayers3.png'> <p>"

       "<img src='https://raw.githubusercontent.com/samyk/samytools/master/eagle/img/throughlayers-ulp.gif'> <br>"

// Version 1.0.0 -- 2017-02-27 initial version (only 2-layer support)

// layers (layer, document, place, origin, name, keepout, restrict)
string top = "t td tn tor tp tk tr ";
string bot = "b bd bn bor bp bk br ";
string notop = "-t -td -tn -tor -tp -tk -tr ";
string nobot = "-b -bd -bn -bor -bp -bk -br ";

string runcmd;
int lVisible[];

void cmd(string s)
{
  runcmd += s + ";";
}

// main
if (!board)
{
  dlgMessageBox("This tool only cycles through board view layers.");
  exit("");
}

board(B)
{
  // determine visible layers
  B.layers(L)
    lVisible[L.number] = L.visible;

  // if top and bottom are visible, go to top
  if (lVisible[1] && lVisible[16])
    cmd("DISPLAY " + top + nobot);

  // only top is visible, go to bottom
  else if (lVisible[1])
    cmd("DISPLAY " + notop + bot);

  // only bottom or top&bottom not visible, show all
  else
    cmd("DISPLAY " + top + bot);
}

exit(runcmd);
